module user {
    yang-version 1;
    namespace "urn:opendaylight:params:xml:ns:yang:user";
    prefix "user";

    revision "2015-01-05" {
        description "Initial revision of user model";
    }
    import school { prefix sch; }

    rpc get-all-user-by-dept-id {
        input {
            leaf dept-id {
                type int32;
                description "部门id";
            }
        }
        output {
            list user-list {
                uses output-user;
                description "用户信息";
            }
        }
    }

    //扩展get-all-user-by-dept-id节点下的output节点的user-list节点，添加一个字段user-teacher
    augment /get-all-user-by-dept-id/output/user-list/ {
            leaf user-teacher {
                type string;
                description "老师";
            }
        }

    /*
    augment sch:school-user-list/sch:user-list {
        uses output-user;
    }
    */

    grouping output-user {
        leaf id {
            type int32;
            description "用户id";
        }
        leaf user-name {
            type string;
            description "用户名";
        }
        leaf user-age {
            type int32;
            description "用户年龄";
        }
        leaf user-address {
            type string;
            description "用户地址";
        }
    }

}
