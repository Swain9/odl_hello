module order-manager {
    yang-version 1;
    namespace "urn:com:maolin:order-manager";
    prefix "odm";

    import order { prefix od; revision-date "2015-01-05";}

    revision "2015-01-05" {
        description "Initial revision of order-manager model";
    }

    rpc getOrderInfo {
        output {
            uses od:order-grouping;
        }
    }
}
