module school {
    yang-version 1;
    namespace "urn:opendaylight:params:xml:ns:yang:school";
    prefix "school";

    //revision-date 2013-07-15;
    import ietf-inet-types { prefix inet; }

    revision "2015-01-05" {
        description "Initial revision of school model";
    }

    grouping school-user-list-grouping {
        container school-user-list {
            list user-list {
                leaf parent-id {
                    type int32;
                    description "用户id";
                }
            }
            leaf school-ip {
                type inet:ipv4-address;
                description "ip 4 地址";
            }
        }
    }

    // USES is not valid for RPC.忘记写output了
    rpc getAllSchoolUserList {
        output {
            uses school-user-list-grouping;
        }
    }

}
